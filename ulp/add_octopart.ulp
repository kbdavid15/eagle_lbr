#include "json.h"

string apiKey = "0c9d5f73";
char gs = 29;
string unicode_regex = "\\u[0-9a-fA-F]{4}";

string chrrep(string str,char a,char b){
	for(int i = 0;i<strlen(str);i++){
		if(str[i]==a){
			str[i] = b;
		}
	}
	return(str);
}

// Unicode is always in format \u0000 (6 characters long)
string convertUnicodeToUtf8(string s) {
	string newString = "";

	if (strstr(s, "\\u") == -1) {
		// not a unicode string
		return s;
	}
	// assumes only one unicode character per string
	int pos = strxstr(s, unicode_regex)-1;
	string code = strsub(s, pos + 2, 4);
	char replace;

	if (code == "00b5") {
		replace = 'µ';
	} else if (code == "03a9") {
		// replace = '';
	} else if (code == "00b0") {
		replace = '°';
	} else if (code == "00b1") {
		// replace = '';
	}

	for (int i = 0; i < strlen(s); i++) {
		// look for 6 character unicode match
		if (i < pos || i >= pos + 6) {
			newString += s[i];
		} else {
			newString += replace;
			i += 5;
		}
	}
	return newString;
}

string octopartSearch(string mpn) {
	string match_url = "http://octopart.com/api/v3/parts/match?";
	string query = "queries=[{\"mpn\": \"" + mpn + "\"}]";
	query += "&apikey=" + apiKey;
	query += "&include[]=specs";

	string Result;
	if (netget(Result, match_url + query) >= 0) {
		// process results
		return(Result);
	}
	else {
		dlgMessageBox(neterror());
	}
	return "";
}

string process_octopart_result(string json_text) {
	string keylist = json_GetKeyList(json_text);
	if (strstr(keylist, "results") < 0) {
		dlgMessageBox("Incorrect result format:\n" + keylist);
		return "Incorrect result format:\n" + keylist;
	}
	string results = json_GetKeyItem(json_text, "results");
	string first_result = json_GetArrayItem(results, 0);	// get the first result items
	string items = json_GetKeyItem(first_result, "items");
	string first_item = json_GetArrayItem(items, 0);	//TODO: Show multiple items for selection
	string specs = json_GetKeyItem(first_item, "specs");
	string mpn = json_GetKeyItem(first_item, "mpn");
	string manuf_obj = json_GetKeyItem(first_item, "manufacturer");
	string manuf = json_GetKeyItem(manuf_obj, "name");

	string ret_val = "manufacturer\t" + manuf + gs;
	ret_val += "mpn\t" + mpn + gs;

	// process specs
	string speclist[];
	strsplit(speclist, json_GetKeyList(specs), '\t');

	for (int i = 0; speclist[i]; i++) {
		string spec_obj = json_GetKeyItem(specs, speclist[i]);
		string display_val = json_GetKeyItem(spec_obj, "display_value");
		ret_val += speclist[i] + "\t" + convertUnicodeToUtf8(display_val) + gs;
	}

	return ret_val;
}

void CreatePartWithAttributes() {

}



void ShowDialogAddToExistingDevice() {
	// get device list
	string devliststr = "";
	string Devices[];
	if (library) {
		library(L) {
			L.devices(D) {
				devliststr += D.name + gs;
			}
			strsplit(Devices, devliststr, gs);
		}
	}
	int selected_dev = 0;
	dlgDialog("Select device to add attributes") {
		dlgHBoxLayout {
			dlgListBox(Devices, selected_dev);
		}
	};
}

void main(void){
	string json_data;
	int idx;
	int array_idx;
	int idx2;
	string strResult;
	string key;
	string mpn_search = "RK73H1ET*3302F";
	string attributes[];
	string packages[];
	string symbols[];
	string listHeader = "Name\tValue";
	int Selected = 0;
	int selected_pkg = 0;
	int selected_sym = 0;
	string searchHistory[];

	// check if being run in library
	if (library) {
		library(L) {
			string pkgstr = "";
			L.packages(P) {	// get packages and populate array
				pkgstr += P.name + gs;
			}
			strsplit(packages, pkgstr, gs);
			string symstr = "";
			L.symbols(S) {	// get packages and populate array
				symstr += S.name + gs;
			}
			strsplit(symbols, symstr, gs);
		}
	}

	dlgDialog("Octopart API Attribute Data") {
		dlgVBoxLayout {
			dlgHBoxLayout {
				dlgStretch(0);
				dlgLabel("Enter part to search Octopart");
				dlgStringEdit(mpn_search, searchHistory, 100);
				dlgPushButton("+&Search") {
					json_data = octopartSearch(mpn_search);
					string results = process_octopart_result(json_data);
					strsplit(attributes, results, gs);
				}
				// dlgSpacing(200);
			}
			dlgHBoxLayout {
				dlgSpacing(500);	// defines the width of the entire dialog
			}
			dlgVBoxLayout {
					dlgLabel("Part Attributes");
					dlgListView(listHeader, attributes, Selected) dlgMessageBox("You have selected " + attributes[Selected]);
				}
			dlgHBoxLayout {

				dlgVBoxLayout {
					dlgLabel("Package");
					dlgListBox(packages, selected_pkg) dlgMessageBox("You have selected " + packages[selected_pkg]);
				}
				dlgVBoxLayout {
					dlgLabel("Symbol");
					// dlgListView("Symbols", symbols, selected_sym) dlgMessageBox("You have selected " + symbols[selected_sym]);
					dlgListBox(symbols, selected_sym) dlgMessageBox("You have selected " + symbols[selected_sym]);
				}
			}
			dlgHBoxLayout {
				dlgPushButton("Add attributes to existing part") {
					dlgAccept();
					ShowDialogAddToExistingDevice();
				}
				dlgPushButton("Create new part") {

				}
			}
		}
	};
}
