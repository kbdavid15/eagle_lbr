#require 6.5100

// Revision history:
//
// 1.00
// - Initial release
//   Using bom.ulp as starting point

string Version = "1.00";

char   Separator = ';'; // 2012-12-04


#usage "en: <b>Import a Bill Of Material</b>\n"
"<p>"
"Generates a project's <i>Bill Of Material</i>&nbsp;&nbsp;including the attributes introduced in"
" version 5.0.0."
"<p>"
"<author>Author: support@cadsoft.de</author><br>"
"<author>Modified to use the new attributes by Carsten Wille.</author><br>"
"<author>.csv export added by Christian Schlittler.</author>"
"<author>Select variant and switch on/off attributes alf@cadsoft.de</author>",
"de: <b>Stückliste exportieren</b>\n"
"<p>"
"Erzeugt die <i>Stückliste</i> (Bill Of Material) eines Projekts, einschließlich der"
" mit Version 5.0.0 neu eingeführten Attribute."
"<p>"
"<author>Autor: support@cadsoft.de</author><br>"
"<author>Modifiziert von Carsten Wille, um die neuen Attribute zu nutzen.</author><br>"
"<author>Export als .csv-Datei durch Christian Schlittler hinzugefügt.</author>"
"<author>Auswählen von Bestückungs-Varianten und Attribute können ein/ausgeschaltet werden alf@cadsoft.de</author>"

// THIS PROGRAM IS PROVIDED AS IS AND WITHOUT WARRANTY OF ANY KIND, EXPRESSED OR IMPLIED

string HelpTextEN =
"<b>How to generate the Bill Of Material</b>\n"
"<p>\n"
"<b>List type</b>\n"
"<p>\n"
"The <i>Bill Of Material</i> can be generated either as a list\n"
"of parts (where every part is listed on a line of its own),\n"
"or as a list of values, where all parts with the same value are grouped\n"
"together in one line. Use the <b><u>P</u>arts</b> and <b><u>V</u>alues</b>\n"
"radio buttons to select the list type.\n"
"<p>\n"
"<b>Output format</b>\n"
"<p>\n"
"Choose between pure ASCII <b><u>T</u>ext</b> format, <b><u>C</u>SV</b> or <b><u>H</u>TML</b>.\n"
;

string HelpTextDE =
"<b>Erzeugen der Stückliste</b>\n"
"<p>\n"
"<b>Listen-Typ</b>\n"
"<p>\n"
"Die <i>Stückliste</i> kann entweder als Liste der Bauteile generiert werden\n"
"(wobei jedes Bauteil in einer eigenen Zeile aufgeführt wird),\n"
"oder als Liste der Werte, wobei alle Bauteile mit dem gleichen Wert in einer Zeile\n"
"zusammengefasst werden. Mit den Radio-Buttons <b><u>B</u>auteile</b> und <b><u>W</u>erte</b>\n"
"kann zwischen den beiden Listen-Typen gewählt werden.\n"
"<p>\n"
"<b>Ausgabeformat</b>\n"
"<p>\n"
"Wählen Sie zwischen reinem ASCII-<b><u>T</u>ext</b>, <b><u>C</u>SV</b> oder <b><u>H</u>TML</b>"
"-Format.\n"
;

string I18N[] = {
	"en\v"
	"de\v"
	,
	"<hr><b>ERROR: No schematic!</b><p>\nThis program can only work in the schematic editor.\v"
	"<hr><b>FEHLER: Kein Schaltplan!</b><p>\nDieses Programm kann nur in einem Schaltplan verwendet"
	" werden.\v"
	,
	"Part\tValue\tDevice\tPackage\tDescription\v"
	"Bauteil\tWert\tDevice\tPackage\tDescription\v"
	,
	"Qty\tValue\tDevice\tPackage\tParts\v"      // 2011-04-08
	"Menge\tWert\tDevice\tGehäuse\tBauteile\v"  // 2011-04-08
	,
	"Partlist exported from %s at %s\v"
	"Stückliste exportiert aus %s am %s\v"
	,
	"Bill Of Material - Preview\v"
	"Stückliste - Vorschau\v"
	,
	"-Close\v"
	"-Schließen\v"
	,
	"Save Bill Of Material\v"
	"Stückliste speichern\v"
	,
	"File '\v"
	"Datei '\v"
	,
	"' exists\n\nOverwrite?\v"
	"' existiert\n\nÜberschreiben?\v"
	,
	"+&Yes\v"
	"+&Ja\v"
	,
	"-&No\v"
	"-&Nein\v"
	,
	"&No\v"
	"&Nein\v"
	,
	"Name already defined!\v"
	"Name ist bereits definiert!\v"
	,
	" Header\v"
	" Spaltenüberschrift\v"
	,
	"&Name:\v"
	"&Name:\v"
	,
	"+OK\v"
	"+OK\v"
	,
	"Name can't be empty!\v"
	"Name kann nicht leer sein!\v"
	,
	"-Cancel\v"
	"-Abbrechen\v"
	,
	"&Headers\v"
	"&Spaltenüberschriften\v"
	,
	"Bill Of Material - Help\v"
	"Stückliste - Hilfe\v"
	,
	"Bill Of Material\v"
	"Stückliste\v"
	,
	"List type\v"
	"Listen-Typ\v"
	,
	"&Parts\v"
	"&Bauteile\v"
	,
	"&Values\v"
	"&Werte\v"
	,
	"Output format\v"
	"Ausgabeformat\v"
	,
	"&Text\v"
	"&Text\v"
	,
	"&CSV\v"
	"&CSV\v"
	,
	"&HTML\v"
	"&HTML\v"
	,
	"+Vie&w\v"
	"+&Vorschau\v"
	,
	"&Save...\v"
	"&Speichern...\v"
	,
	"H&elp\v"
	"H&ilfe\v"
	,
	"Current &variant \v"
	"Aktuelle &Variante \v"
	,
	"List &attributes\v"
	"&Attribute auflisten\v"
};
int Language = strstr (I18N [0], language ()) / 3;


string tr (string s)
{
	string t = lookup (I18N, s, Language, '\v');
	return t ? t : s;
}


if (!schematic)
{
	dlgMessageBox (usage + tr ("<hr><b>ERROR: No schematic!</b><p>\nThis program can only work in"
	" the schematic editor."));
	exit (1);
}

string SeparatorString;
int     NumParts;
numeric string Lines[];
numeric string PartName[];
string  PartValue[], PartDevice[], PartPackage[], PartHeadline[];
numeric string PartDescription [];
int     PartValueOn[];
int     Selected;

string CurrentVariant = "";
string Variants[] = { "" };  // 2012-04-16
int    cntVD = 0;
int    VDsel = 0;


// cwi: Added arrays for an arbitraty number of attributes.
int UseAttributes = 1;
int FoundAttributes = 0;            // # of different attribute names found in schematic.
numeric string AttributesList[];    // Sorted list of all attributes found in the schematic.
numeric string PartAttributes[];    // Adjusted list of attributes per part.

enum { ltParts, ltValues };         // List Types
enum { ofText, ofCSV, ofHTML };     // Output Formats
int ListType = 0;
int OutputFormat = 0;


string StripWhiteSpace (string s)
{
	while (s && isspace (s[0]))
	s = strsub (s, 1);
	while (s && isspace (s[strlen (s) - 1]))
	s = strsub (s, 0, strlen (s) - 1);
	return s;
}

string ReplaceTabs(string s)
{
	int i;
	while ((i = strchr(s, '\t')) >= 0)
	s = strsub(s, 0, i) + "\\t" + strsub(s, i + 1);
	return s;
}

string SplitResults[];
int SplitResultLength = 0;
void SplitPreserveQuotes(string splitStr, char separator)
{
	int start = 0;
	int inQuotes = -1;	// false
	int inputLength = strlen(splitStr);
	int resultCnt = 0;
	for (int i = 0; splitStr[i]; i++) 
	{
		if (splitStr[i] == '\"') {
			inQuotes *= -1; // toggle state
		}
		if (i == (inputLength - 1))
		{
			SplitResults[resultCnt++] = strsub(splitStr, start);	// add rest of data
		}
		else if (splitStr[i] == separator && (inQuotes < 0))
		{
			SplitResults[resultCnt++] = strsub(splitStr, start, i-start);
			start = i + 1;
		}
	}
	SplitResultLength = resultCnt;
}


// Collect part data from the schematic.
//
// Arguments: -
//
// Returns:   NumParts            - # of found parts
//            PartName[]
//            PartValue[]
//            PartDevice[]
//            PartPackage[]
//            PartHeadline[]
//            PartDescription []
//            PartValueOn[]      - 0=part value off, 1= part value on, 2=override with attr. VAL
//            FoundAttributes     - # of different attribute names found in schematic.
//            AttributesList[]   - Sorted list of all attributes found in the schematic.
//            PartAttributes[]   - Adjusted list of attributes per part.

void CollectPartData (string filePath)
{
	string lines[];
	string attr[];
	int nLines = fileread(lines, filePath);
		// First, collect the names of all available attributes, found in header row. Attrib starts after col 5
	string header[];
	int n = strsplit(header, lines[0], ',');
	FoundAttributes = 0;	
	for (int i = 5; header[i]; i++) 
	{
		AttributesList[FoundAttributes] = header[i];
		FoundAttributes ++;
	}
	sort (FoundAttributes, AttributesList);
	
	NumParts = 0;
	for (i = 0; i < nLines; ++i) {
		// split line by character separator
		string col[];
		//int n = strsplit(col, lines[i], ',');
		SplitPreserveQuotes(lines[i], ',');
		if (SplitResults[0] == "Part") {
			continue;	// skip header, if present
		}
		PartName[NumParts] = SplitResults[0];
		PartValue[NumParts] = SplitResults[1];
		PartDevice[NumParts] = SplitResults[2];
		PartPackage[NumParts] = SplitResults[3];
		PartHeadline[NumParts] = SplitResults[4];
		
		// Zero all strings
		for (i = 0; i < FoundAttributes; i ++)
            attr[i] = "";
		for (i = 0; i < FoundAttributes; i ++)
		{
			if (SplitResults[4+i] != "" && (4+i) < SplitResultLength)
			{
				attr[i] = SplitResults[4+i];
				break;
			}
		}
		PartAttributes[NumParts] = strjoin(attr, Separator);
		NumParts++;
	}
	
}


void GeneratePartList(void)
{
	int NumLines = 0;
	string attr[], s;

	if (UseAttributes) s = strjoin(AttributesList, '\t');
	Lines[NumLines ++] = tr ("Part\tValue\tDevice\tPackage\tDescription\t") + s;
	for (int i = 0; i < NumParts; i ++)
	{
		strsplit (attr, PartAttributes[i], Separator);
		if (UseAttributes) s = strjoin(attr, '\t');
		Lines[NumLines] = PartName[i] + "\t" + PartValue[i] + "\t" + PartDevice[i] + "\t" +
		PartPackage[i] + "\t" + PartHeadline[i] + "\t" + s;
		NumLines ++;
	}
	Lines[NumLines] = "";
}



string MakeListHeader (void)
{
	string s;
	schematic(SCH)
	sprintf (s, tr ("Partlist exported from %s at %s"), SCH.name, t2string (time ()));
	return s;
}

string MakeListText(void)
{
	int l, Width [];
	string List;
	int numHeaders;

	for (l = 0; Lines[l]; l ++)
	{
		string a [];
		for (int n = strsplit (a, Lines[l], '\t'); n --; )
		Width [n] = max (Width [n], strlen (a [n]));
	}

	List = MakeListHeader () + "\n\n";

	for (l = 0; Lines[l]; l ++)
	{
		string line, a [];

		int n = strsplit (a, Lines[l], '\t');
		if (l == 0)
		numHeaders = n;
		else
		n = numHeaders; // for the hidden key!
		for (int i = 0; i < n; i ++)
		{
			string s;

			sprintf (s, "%s%-*s", line ? " " : "", Width [i], a [i]);
			line += s;
		}
		List += line + "\n";
	}
	return List;
}


// 2008-11-24 Christian Schlittler:
// Make comma-serparated list, with all values double-quoted.

string MakeListCSV (void)
{
	string List;
	int numHeaders;

	for (int l = 0; Lines[l]; l ++)
	{
		string a [];
		int n = strsplit (a, Lines[l], '\t');
		if (l == 0)
		numHeaders = n;
		else
		n = numHeaders; // for the hidden key!
		for (int i = 0; i < n; i ++)
		List += "\"" + a[i] + "\"" + SeparatorString;
		List += "\n";
	}
	return List;
}


string MakeListHTML (void)
{
	string List;
	int numHeaders;

	List = "<b>" + MakeListHeader() + "</b>\n<p>\n";
	List += "<table>\n";
	for (int l = 0; Lines[l]; l++)
	{
		List += "<tr>";
		string a [];
		int n = strsplit (a, Lines[l], '\t');
		if (l == 0)
		numHeaders = n;
		else
		n = numHeaders; // for the hidden key!
		for (int i = 0; i < n; i ++)
		{
			if (l == 0)
			a[i] = "<b>" + a[i] + "</b>";
			List += "<td>" + a[i] + "</td>";
		}
		List += "</tr>\n";
	}
	List += "</table>\n";
	return List;
}


string MakeList (void)
{
	switch (OutputFormat)
	{
	case ofText: return MakeListText(); break;
	case ofCSV:  return MakeListCSV(); break;
	case ofHTML: return MakeListHTML(); break;
	}
	return "";
}


void ViewList (void)
{
	dlgDialog (tr ("Bill Of Material - Preview"))
	{
		string s = MakeList ();
		if (OutputFormat == ofText || OutputFormat == ofCSV)
		s = "<pre>" + s + "</pre>";
		dlgHBoxLayout dlgSpacing (400);
		dlgHBoxLayout
		{
			dlgVBoxLayout dlgSpacing (300);
			dlgTextView (s);
		}
		dlgHBoxLayout
		{
			dlgStretch (1);
			dlgPushButton (tr ("-Close")) dlgReject ();
		}
	};
}


void SaveList (void)
{
	// 2008-11-24 cwi:
	// - Added new format extension .csv
	// - Changed from .bom to .txt for text format.
	string FileName;
	string FileExt;

	switch (OutputFormat)
	{
	case ofText: FileExt = ".txt"; break;
	case ofHTML: FileExt = ".html"; break;
	case ofCSV:  FileExt = ".csv"; break;
	}
	schematic(SCH) FileName = filesetext (SCH.name, FileExt);
	FileName = dlgFileSave (tr ("Save Bill Of Material"), FileName);
	if (FileName)
	{
		string a [];
		if (!fileglob (a, FileName) || dlgMessageBox (tr ("File '") + FileName +
					tr ("' exists\n\nOverwrite?"), tr("+&Yes"), tr("-&No")) == 0)
		{
			output (FileName, "wt")
			{
				printf ("%s", MakeList ()); // using "%s" to avoid problems if list contains any '%'
			}
		}
	}
}

void UpdatePartAttributes()
{
	output("change-attr.scr", "wt")
	{
		schematic(SCH)
		{
			SCH.allparts (P)
			{
				printf("ATTRIBUTE '%s' '%s' '%s';\n", P.name, "", "");
			}
		}
	}	
}

void main(void){
	string attributes[];
	string packages[];
	string symbols[];
	string listHeader = "Name\tValue";
	int Selected = 0;
	int selected_pkg = 0;
	int selected_sym = 0;
	string import_bom_path = "";
	
	schematic(SCH) {
		sprintf(SeparatorString, "%c", Separator);
		CurrentVariant = variant();
		SCH.variantdefs(VD) {
			if (CurrentVariant == VD.name) VDsel = cntVD;
			sprintf(Variants[cntVD], "%s", VD.name);
			cntVD++;
		}
	}
	
	import_bom_path = dlgFileOpen("Import BOM", "", "*.csv");
	
	setvariant(CurrentVariant);
	CollectPartData(import_bom_path);
	GeneratePartList();
	
	dlgDialog (tr ("Bill Of Material"))
	{
		dlgHBoxLayout {
			dlgLabel(tr ("Current &variant "));
			dlgComboBox(Variants, VDsel) {
				CurrentVariant = Variants[VDsel];
				setvariant(CurrentVariant);
			}
			dlgStretch(1);
		}
		dlgListView ("", Lines, Selected);		
		dlgHBoxLayout  {
			dlgPushButton (tr ("+Vie&w"))    ViewList ();
			dlgPushButton (tr ("&Save...")) SaveList ();
			dlgPushButton (tr ("-Close"))   dlgAccept ();
			dlgStretch(1);
			dlgLabel("Version " + Version);
		}
	};
}
